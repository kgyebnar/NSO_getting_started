module acl_lab {
  namespace "http://com/example/acl_lab";
  prefix acl_lab;

  import ietf-inet-types {
    prefix inet;
  }
  import tailf-ncs {
    prefix ncs;
  }

import tailf-common { 
    prefix tailf; 
    }

  augment /ncs:services {

  list acl_lab {
    key "ACL_Name ACL_Direction";
    uses ncs:service-data;
    ncs:servicepoint "acl_lab";

    leaf ACL_Name {
	type string;
	tailf:info "ACL-NAME string";

	}

    leaf ACL_Direction {
	type enumeration{
        enum "in";
        enum "out";
	tailf:info "ACL DIRECTION";
	}
    }
    
    list devices {
      key device_name;

    leaf device_name {
      type leafref {
        path "/ncs:devices/ncs:device/ncs:name";
      }
    }

	list interfaces {
	    key "interface_type interface_number";
	
	leaf interface_type {
          type enumeration{
            enum "FastEthernet";
            enum "GigabitEthernet";
            enum "TenGigEthernet";
            enum "Loopback";
          }
        }

	leaf interface_number {
          type string;
    	}
	}
    }
    }
  } // augment /ncs:services {
}
