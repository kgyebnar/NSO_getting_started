module nso-interface {
  namespace "http://com/example/nsointerface";
  prefix nso-interface;

  import ietf-inet-types {
    prefix inet;
  }
  import tailf-ncs {
    prefix ncs;
  }

  augment /ncs:services {
  list nso-interface {
    key name;

    uses ncs:service-data;
    ncs:servicepoint "nso-interface";

    leaf name {
      type string;
    }

    // may replace this with other ways of refering to the devices.
    leaf-list device {
      type leafref {
        path "/ncs:devices/ncs:device/ncs:name";
      }
    }
  }
  } // augment /ncs:services {
}
